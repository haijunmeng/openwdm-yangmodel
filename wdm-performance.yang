module wdm-performance {
    yang-version 1.1;
    namespace "urn:ccsa:yang:wdm-performance";
    prefix wdm-pm;

    import ietf-yang-types {
        prefix yang;
    }
    import wdm-yang-types {
        prefix wdm-type;
    }
    
    organization "xxx";
    contact "xxx";
    description "This module defines an interface for managing performances.";
    revision 2019-02-13 {
        description "Initial revision.";
        reference "RFC xxx";
    }
    /*
    * Groupings
    */   
    grouping performances {
        list performance {
            key 'pm-parameter-name start-time';
            leaf pm-parameter-name {
                type string {
                    length "1..64";
                }
                description "pm-parameter-name";
            }
            leaf start-time {
                type yang:date-and-time;
                description "start-time";
            }
            leaf object-name {
                mandatory true;
                type string {
                    length "1..64";
                }
                config false;
                description "object-name";
            }
            leaf object-type {
                mandatory true;
                type string {
                    length "1..64";
                }
                config false;
                description "object-type";
            }
            leaf granularity {
                type wdm-type:granularity;
                config false;
                description "granularity";
            }
            leaf digital-pm-value {
                type wdm-type:real;
                config false;
                description "digital-pm-value";
            }
            container analog-pm-value {
                leaf max-value {
                    type wdm-type:real;
                    description "max-value";
                }
                leaf min-value {
                    type wdm-type:real;
                    description "min-value";
                }
                leaf average-value {
                    type wdm-type:real;
                    description "average-value";
                }
                leaf current-value {
                    type wdm-type:real;
                    description "current-value";
                }
                description "analog-pm-value";
            }
            description "performance list";
        }
        description "performances";
    }
    /*
    * The data tree
    */
    container performances {
        uses performances;
        description "performances container";
    }
    /*
    * Operations
    */
    rpc get-history-performance-monitoring-data {
        description "none";
            input {
                leaf start-time {
                    mandatory true;
                    type yang:date-and-time;
                    description "none";
                }
                leaf end-time {
                    mandatory true;
                    type yang:date-and-time;
                    description "none";
                }
                leaf object-name {
                    type string {
                        length "1..64";
                    }
                    description "none";
                }
                leaf granularity {
                    mandatory true;
                    type wdm-type:granularity;
                    description "none";
                }
                leaf pm-parameter-name {
                    type string {
                        length "1..64";
                    }
                    description "none";
                }
            }
            output {
                container performances {
                    uses performances;
                    description "none";
                } 
            }
    }
}
